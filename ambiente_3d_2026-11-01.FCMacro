# -*- coding: utf-8 -*-
# Macro gerada pelo Medidor GLM em 01/11/2026, 17:03:10
# FreeCAD: Macro > Macros... > escolha este arquivo > Executar
# Cada ambiente vira uma pasta; dentro, uma pasta por parede com a parede 3D, notas, pontos e fotos.
import FreeCAD as App, Part, json, base64, os, tempfile
V = App.Vector
D = json.loads(r'''{"titulo":"ambiente 3d","endereco":"nair","ambientes":[{"nome":"Sala","H":2450,"fechado":true,"pts":[[0,0],[4000,0],[4000,-2000],[3000,-2000],[3000,-5000],[0,-5000],[0,0]],"obs":"","ws":[{"nome":"A","ax":9.18485099360515e-13,"ay":0,"ux":1,"uy":0,"L":4000,"esq":true,"ang":0,"canto":90,"eS":true,"eE":true,"obs":"","fotos":[]},{"nome":"B","ax":4000.000000000001,"ay":0,"ux":6.123233995736766e-17,"uy":-1,"L":2000,"esq":true,"ang":-90,"canto":90,"eS":true,"eE":true,"obs":"","fotos":[]},{"nome":"C","ax":4000.000000000001,"ay":-2000,"ux":-1,"uy":-1.2246467991473532e-16,"L":1000,"esq":true,"ang":-180,"canto":270,"eS":true,"eE":false,"obs":"","fotos":[]},{"nome":"D","ax":3000.000000000001,"ay":-2000.0000000000002,"ux":6.123233995736766e-17,"uy":-1,"L":3000,"esq":true,"ang":-90,"canto":90,"eS":false,"eE":true,"obs":"","fotos":[]},{"nome":"E","ax":3000.000000000001,"ay":-5000,"ux":-1,"uy":-1.2246467991473532e-16,"L":3000,"esq":true,"ang":-180,"canto":90,"eS":true,"eE":true,"obs":"","fotos":[]},{"nome":"F","ax":9.18485099360515e-13,"ay":-5000,"ux":-1.8369701987210297e-16,"uy":1,"L":5000,"esq":true,"ang":90.00000000000001,"canto":90,"eS":true,"eE":true,"obs":"","fotos":[]}],"moveis":[{"id":"mvwrn25cv5w63","k":"inferior","tipo":"inferior","parede":"mvwpz404hmoq1","dist":30,"larg":800,"alt":870,"prof":580,"z":0,"portas":2,"gavetas":0,"prats":1,"base":1,"nome":"","p":5},{"id":"mvwrouu9anrmy","k":"inferior","tipo":"inferior","parede":"mvwpz404hmoq1","dist":830,"larg":800,"alt":870,"prof":580,"z":0,"portas":2,"gavetas":0,"prats":1,"base":1,"nome":"","p":5},{"id":"mvwrp791c183x","k":"inferior","tipo":"inferior","parede":"mvwpz404hmoq1","dist":1630,"larg":800,"alt":870,"prof":580,"z":0,"portas":2,"gavetas":0,"prats":1,"base":1,"nome":"","p":5},{"id":"mvwrpwwr1rdrh","k":"inferior","tipo":"inferior","parede":"mvwpz404hmoq1","dist":2430,"larg":600,"alt":870,"prof":580,"z":0,"portas":0,"gavetas":4,"prats":0,"base":1,"nome":"","tamp_dir":false,"tamp_esq":false,"p":5},{"id":"mvwrrjp1373xu","k":"aereo","tipo":"aereo","parede":"mvwpz404hmoq1","dist":30,"larg":500,"alt":700,"prof":350,"z":1500,"portas":1,"gavetas":0,"prats":1,"base":0,"nome":"","p":5},{"id":"mvwrsgnu92j21","k":"aereo","tipo":"aereo","parede":"mvwpz404hmoq1","dist":2660,"larg":400,"alt":700,"prof":350,"z":1500,"portas":1,"gavetas":0,"prats":1,"base":0,"nome":"","p":5},{"id":"mvxuqi2jky5yj","k":"canto_l_gr_esq","tipo":"canto_l_gr_esq","parede":"mvwpz404i8ihd","dist":0,"larg":1100,"alt":2400,"prof":1100,"z":0,"portas":2,"gavetas":0,"prats":2,"base":1,"nome":"","p":1},{"id":"mvxur305su4eq","k":"guarda_roupa","tipo":"guarda_roupa","parede":"mvwpz404i8ihd","dist":1100,"larg":880,"alt":2400,"prof":580,"z":0,"portas":2,"gavetas":2,"prats":2,"base":1,"nome":"","p":1},{"id":"mvxzgxwefnfrw","k":"inferior","tipo":"inferior","larg":800,"alt":870,"prof":580,"z":0,"portas":2,"gavetas":0,"prats":1,"base":1,"parede":"mvwpz404x5cn4","dist":2100,"nome":"","p":0}],"avulsas":[{"id":"mvwvwnw1y3fmf","k":"tampo","parede":"mvwpz404hmoq1","dist":30,"comp":3000,"prof":618,"z":870,"esp":15,"faixa":70,"eng":true,"mat":"","nome":"","fitas":[1,1,1,1],"p":5},{"id":"mvy99tgg3lj1n","k":"cabeceira","parede":"mvwpz404mlfjd","dist":0,"larg":2350,"alt":1100,"esp":15,"faixa":70,"ma_baixo":150,"z":0,"eng_esq":false,"eng_dir":false,"mat":"","nome":"","fitas":[1,1,1,1],"p":4}],"itens":[{"nome":"Janela","tipo":"janela","ab":true,"p":5,"dist":600,"alt":1100,"larg":2000,"h":1100,"obs":"","dob":"e","abre":"dentro","acab":"","modelo":"","mods":"","v220":false},{"nome":"Porta","tipo":"porta","ab":true,"p":0,"dist":200,"alt":0,"larg":820,"h":2100,"obs":"","dob":"e","abre":"dentro","acab":"","modelo":"","mods":"","v220":false},{"nome":"Interruptor","tipo":"interruptor","ab":false,"p":0,"dist":1150,"alt":1200,"larg":0,"h":0,"obs":"","dob":"e","abre":"dentro","acab":"","modelo":"","mods":"IT","v220":false}]}]}''')
ESP = 150.0  # espessura de parede desenhada (mm), para fora da medida interna
PASTA = tempfile.mkdtemp(prefix='medidor_')

def caixa(w, u0, u1, n0, n1, z0, z1):
    # u: ao longo da parede; n: para fora (positivo) ou para dentro do ambiente (negativo)
    if w['esq']:
        s0, s1 = n0, n1
    else:
        s0, s1 = -n1, -n0
    b = Part.makeBox(u1 - u0, s1 - s0, z1 - z0)
    u = V(w['ux'], w['uy'], 0)
    l = V(-w['uy'], w['ux'], 0)
    b.Placement = App.Placement(V(w['ax'], w['ay'], 0) + u * u0 + l * s0 + V(0, 0, z0), App.Rotation(V(0, 0, 1), w['ang']))
    return b

def visual(o, cor, transp=0):
    try:
        o.ViewObject.ShapeColor = cor
        o.ViewObject.Transparency = transp
    except Exception:
        pass

def grupo(nome, pai=None):
    g = doc.addObject('App::DocumentObjectGroup', 'Grupo')
    g.Label = nome
    if pai:
        pai.addObject(g)
    return g

def nota(texto, nome, pai):
    try:
        t = doc.addObject('App::TextDocument', 'Notas')
        t.Text = texto
        t.Label = nome
        pai.addObject(t)
    except Exception as e:
        App.Console.PrintWarning('Nota nao criada: %s\n' % e)

def foto(w, f, pai):
    caminho = os.path.join(PASTA, f['arq'])
    with open(caminho, 'wb') as fh:
        fh.write(base64.b64decode(f['b64']))
    try:
        import Image
    except Exception:
        pass
    try:
        o = doc.addObject('Image::ImagePlane', 'Foto')
    except Exception as e:
        App.Console.PrintWarning('Foto nao inserida (%s). Arquivo em %s\n' % (e, caminho))
        return
    o.ImageFile = caminho
    o.XSize = f['lx']
    o.YSize = f['ly']
    o.Label = f['nome']
    u = V(w['ux'], w['uy'], 0)
    esq = V(-w['uy'], w['ux'], 0)
    dentro = esq * (-1 if w['esq'] else 1)
    centro = V(w['ax'], w['ay'], 0) + u * f['u'] + dentro * 6 + V(0, 0, f['z'])
    giro = w['ang'] if w['esq'] else w['ang'] + 180
    o.Placement = App.Placement(centro, App.Rotation(V(0, 0, 1), giro).multiply(App.Rotation(V(1, 0, 0), 90)))
    pai.addObject(o)

def caixa_comp(w, partes):
    return Part.makeCompound([caixa(w, *pp) for pp in partes])

def modelo(w, it, gp):
    d, z, L, Hh, t = it['dist'], it['alt'], it['larg'], it['h'], it['tipo']
    u = V(w['ux'], w['uy'], 0)
    esq = V(-w['uy'], w['ux'], 0)
    dentro = esq * (-1 if w['esq'] else 1)
    base = V(w['ax'], w['ay'], 0) + u * d + V(0, 0, z)
    if t == 'porta' and L > 0 and Hh > 0:
        m = 40.0
        batente = caixa_comp(w, [(d, d + m, -10, ESP + 10, z, z + Hh), (d + L - m, d + L, -10, ESP + 10, z, z + Hh), (d, d + L, -10, ESP + 10, z + Hh - m, z + Hh)])
        o = doc.addObject('Part::Feature', 'Batente'); o.Shape = batente; o.Label = 'Batente porta'; visual(o, (0.55, 0.38, 0.22)); gp.addObject(o)
        f = doc.addObject('Part::Feature', 'Porta')
        f.Shape = caixa(w, d + m + 3, d + L - m - 3, ESP / 2 - 17, ESP / 2 + 18, z + 10, z + Hh - m - 3)
        f.Label = 'Folha %dx%d' % (round(L - 2 * m - 6), round(Hh - m - 13)); visual(f, (0.72, 0.52, 0.32)); gp.addObject(f)
        return f
    if t == 'janela' and L > 0 and Hh > 0:
        m = 50.0
        partes = [(d, d + m, ESP / 2 - 30, ESP / 2 + 30, z, z + Hh), (d + L - m, d + L, ESP / 2 - 30, ESP / 2 + 30, z, z + Hh),
                  (d, d + L, ESP / 2 - 30, ESP / 2 + 30, z, z + m), (d, d + L, ESP / 2 - 30, ESP / 2 + 30, z + Hh - m, z + Hh)]
        if L > 800:
            partes.append((d + L / 2 - m / 2, d + L / 2 + m / 2, ESP / 2 - 30, ESP / 2 + 30, z, z + Hh))
        o = doc.addObject('Part::Feature', 'Caixilho'); o.Shape = caixa_comp(w, partes); o.Label = 'Caixilho janela'; visual(o, (0.82, 0.84, 0.86)); gp.addObject(o)
        v = doc.addObject('Part::Feature', 'Vidro'); v.Shape = caixa(w, d + m, d + L - m, ESP / 2 - 3, ESP / 2 + 3, z + m, z + Hh - m)
        v.Label = 'Vidro'; visual(v, (0.55, 0.78, 0.92), 70); gp.addObject(v)
        return o
    if t in ('tomada', 'interruptor'):
        o = doc.addObject('Part::Feature', 'Placa'); o.Shape = caixa(w, d - 38, d + 38, -9, 0, z - 60, z + 60)
        visual(o, (0.95, 0.95, 0.93)); gp.addObject(o); return o
    if t == 'luz':
        o = doc.addObject('Part::Feature', 'Luz'); o.Shape = caixa(w, d - 50, d + 50, -12, 0, z - 50, z + 50)
        visual(o, (0.98, 0.86, 0.3)); gp.addObject(o); return o
    if t == 'ar':
        o = doc.addObject('Part::Feature', 'Ar'); o.Shape = caixa(w, d - 90, d + 90, -20, 0, z - 90, z + 90)
        visual(o, (0.09, 0.65, 0.58)); gp.addObject(o); return o
    tubos = {'agua': (12.5, 60, (0.11, 0.56, 0.84)), 'esgoto': (25.0, 50, (0.48, 0.32, 0.19)), 'gas': (10.0, 60, (0.95, 0.75, 0.1))}
    if t in tubos:
        r, comp, cor = tubos[t]
        o = doc.addObject('Part::Feature', 'Cano'); o.Shape = Part.makeCylinder(r, comp, base, dentro)
        visual(o, cor); gp.addObject(o); return o
    o = doc.addObject('Part::Feature', 'Ponto'); o.Shape = Part.makeSphere(40, base)
    visual(o, (0.4, 0.4, 0.4)); gp.addObject(o); return o

CORES = {'tomada': (0.84, 0.6, 0.0), 'interruptor': (0.79, 0.5, 0.0), 'luz': (0.88, 0.7, 0.0), 'agua': (0.11, 0.56, 0.84),
         'esgoto': (0.48, 0.32, 0.19), 'gas': (0.84, 0.27, 0.11), 'ar': (0.09, 0.65, 0.58)}

doc = App.newDocument('Medicao')
doc.Label = D['titulo']
for a in D['ambientes']:
    ga = grupo(a['nome'])
    H = float(a['H'])
    if a['obs']:
        nota(a['obs'], 'Notas - ' + a['nome'], ga)
    gps = []
    for i, w in enumerate(a['ws']):
        gp = grupo('Parede %s - %d mm' % (w['nome'], round(w['L'])), ga)
        gps.append(gp)
        if w['L'] <= 0:
            continue
        s = caixa(w, -ESP * w['eS'], w['L'] + ESP * w['eE'], 0, ESP, 0, H)
        for it in a['itens']:
            if it['p'] == i and it['ab'] and it['tipo'] != 'viga' and it['larg'] > 0 and it['h'] > 0:
                s = s.cut(caixa(w, it['dist'], it['dist'] + it['larg'], -ESP, 2 * ESP, it['alt'], it['alt'] + it['h']))
        o = doc.addObject('Part::Feature', 'Parede')
        o.Shape = s
        o.Label = 'Parede %s' % w['nome']
        try:
            o.addProperty('App::PropertyLength', 'Comprimento', 'Medicao')
            o.Comprimento = w['L']
            o.addProperty('App::PropertyAngle', 'CantoNoFim', 'Medicao')
            o.CantoNoFim = w['canto']
            o.addProperty('App::PropertyString', 'Nota', 'Medicao')
            o.Nota = w['obs']
        except Exception:
            pass
        gp.addObject(o)
        visual(o, (0.86, 0.84, 0.79), 35)
        if w['obs']:
            nota(w['obs'], 'Notas parede ' + w['nome'], gp)
        if w['fotos']:
            gf = grupo('Fotos parede ' + w['nome'], gp)
            for f in w['fotos']:
                foto(w, f, gf)
    for it in a['itens']:
        if it['p'] < 0:
            continue
        w = a['ws'][it['p']]
        if it['ab']:
            rot = '%s %dx%d - dist %d / h %d' % (it['nome'], round(it['larg']), round(it['h']), round(it['dist']), round(it['alt']))
        else:
            rot = '%s - dist %d / h %d' % (it['nome'], round(it['dist']), round(it['alt']))
        if it['obs']:
            rot += ' - ' + it['obs']
        if it['tipo'] == 'viga' and it['larg'] > 0 and it['h'] > 0:
            o = doc.addObject('Part::Feature', 'Viga')
            o.Shape = caixa(w, it['dist'], it['dist'] + it['larg'], -100, 0, it['alt'], it['alt'] + it['h'])
            visual(o, (0.55, 0.31, 0.69), 50)
            gps[it['p']].addObject(o)
        elif it['tipo'] in ('porta', 'janela'):
            if it['larg'] <= 0 or it['h'] <= 0:
                continue
            o = modelo(w, it, gps[it['p']])
        elif it['ab']:
            continue
        else:
            o = modelo(w, it, gps[it['p']])
        o.Label = rot
    if a['fechado'] and len(a['pts']) > 3:
        try:
            f = Part.Face(Part.makePolygon([V(x, y, 0) for x, y in a['pts']]))
            o = doc.addObject('Part::Feature', 'Piso')
            o.Shape = f
            o.Label = 'Piso ' + a['nome']
            ga.addObject(o)
            visual(o, (0.75, 0.82, 0.77), 20)
        except Exception as e:
            App.Console.PrintWarning('Piso nao criado: %s\n' % e)
doc.recompute()
try:
    import FreeCADGui
    FreeCADGui.activeDocument().activeView().viewIsometric()
    FreeCADGui.SendMsgToActiveView('ViewFit')
except Exception:
    pass
App.Console.PrintMessage('Medicao montada. Salve o arquivo (.FCStd) para guardar as fotos junto do projeto.\n')
